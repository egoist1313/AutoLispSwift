;version 2.10
(defun C:POPER (/ dcl_id mode_points mode_vectors h_scale l_scale text_height round_to slope_round_to slope_unit use_text_height show_lengths show_slopes result OSZ OSH PCoords point_count pt delta_y final_height top_point_height bottom_point_height top_point_length bottom_point_length prev_x dist original_unitmode original_dimzin original_lunits original_luprec heights original_PCoords temp_points selected_entities profile_polyline intersections prev_pt prev_height sorted_PCoords sorted_heights i pt1 pt2 delta_x final_height1 final_height2 slope slope_text text_x mid_point mid_height top_point_slope bottom_point_slope filtered_entities entity_type temp_point_ent x_coords unique_entities text_entity text_content)
    (vl-load-com)
    (setq dcl_id (load_dialog "poper.dcl"))
    (if (not (new_dialog "poper_settings" dcl_id))
        (progn (princ "\nОшибка загрузки DCL-файла.") (exit))
    )

    (if (null (getenv "ZZ_MODE")) (setenv "ZZ_MODE" "points"))
    (if (null (getenv "ZZ_H_SCALE")) (setenv "ZZ_H_SCALE" "10"))
    (if (null (getenv "ZZ_L_SCALE")) (setenv "ZZ_L_SCALE" "1"))
    (if (null (getenv "ZZ_TEXT_HEIGHT")) (setenv "ZZ_TEXT_HEIGHT" "2.5"))
    (if (null (getenv "ZZ_ROUND_TO")) (setenv "ZZ_ROUND_TO" "0"))
    (if (null (getenv "ZZ_SLOPE_ROUND_TO")) (setenv "ZZ_SLOPE_ROUND_TO" "0"))
    (if (null (getenv "ZZ_SLOPE_UNIT")) (setenv "ZZ_SLOPE_UNIT" "permille"))
    (if (null (getenv "ZZ_USE_TEXT_HEIGHT")) (setenv "ZZ_USE_TEXT_HEIGHT" "1"))
    (if (null (getenv "ZZ_SHOW_LENGTHS")) (setenv "ZZ_SHOW_LENGTHS" "1"))
    (if (null (getenv "ZZ_SHOW_SLOPES")) (setenv "ZZ_SHOW_SLOPES" "1"))

    (set_tile "mode_points" (if (eq (getenv "ZZ_MODE") "points") "1" "0"))
    (set_tile "mode_vectors" (if (eq (getenv "ZZ_MODE") "vectors") "1" "0"))
    (set_tile "h_scale" (getenv "ZZ_H_SCALE"))
    (set_tile "l_scale" (getenv "ZZ_L_SCALE"))
    (set_tile "text_height" (getenv "ZZ_TEXT_HEIGHT"))
    (set_tile "round_to" (getenv "ZZ_ROUND_TO"))
    (set_tile "slope_round_to" (getenv "ZZ_SLOPE_ROUND_TO"))
    (set_tile "slope_unit" (cond ((eq (getenv "ZZ_SLOPE_UNIT") "permille") "0")
                                 ((eq (getenv "ZZ_SLOPE_UNIT") "degrees") "1")
                                 ((eq (getenv "ZZ_SLOPE_UNIT") "ratio") "2")
                                 (t "0")))
    (set_tile "use_text_height" (getenv "ZZ_USE_TEXT_HEIGHT"))
    (set_tile "show_lengths" (getenv "ZZ_SHOW_LENGTHS"))
    (set_tile "show_slopes" (getenv "ZZ_SHOW_SLOPES"))

    (action_tile "accept"
        "(progn
            (setq mode_points (get_tile \"mode_points\"))
            (setq mode_vectors (get_tile \"mode_vectors\"))
            (if (and (/= mode_points \"1\") (/= mode_vectors \"1\"))
                (progn (alert \"Выберите режим: По точкам или По векторам.\") (exit)))
            (if (= mode_points \"1\") (setenv \"ZZ_MODE\" \"points\") (setenv \"ZZ_MODE\" \"vectors\"))
            (setq h_scale (get_tile \"h_scale\"))
            (setq l_scale (get_tile \"l_scale\"))
            (setq text_height (get_tile \"text_height\"))
            (setq round_to_index (atoi (get_tile \"round_to\")))
            (setq round_to (nth round_to_index '(\"2\" \"3\")))
            (setq slope_round_to (get_tile \"slope_round_to\"))
            (setq slope_unit_index (atoi (get_tile \"slope_unit\")))
            (setq slope_unit (nth slope_unit_index '(\"permille\" \"degrees\" \"ratio\")))
            (setq use_text_height (get_tile \"use_text_height\"))
            (setq show_lengths (get_tile \"show_lengths\"))
            (setq show_slopes (get_tile \"show_slopes\"))
            (done_dialog 1)
        )"
    )
    (action_tile "cancel" "(done_dialog 0)")

    (setq result (start_dialog))
    (unload_dialog dcl_id)

    (if (= result 1)
        (progn
            (setenv "ZZ_H_SCALE" h_scale)
            (setenv "ZZ_L_SCALE" l_scale)
            (setenv "ZZ_TEXT_HEIGHT" text_height)
            (setenv "ZZ_ROUND_TO" (itoa round_to_index))
            (setenv "ZZ_SLOPE_ROUND_TO" slope_round_to)
            (setenv "ZZ_SLOPE_UNIT" slope_unit)
            (setenv "ZZ_USE_TEXT_HEIGHT" use_text_height)
            (setenv "ZZ_SHOW_LENGTHS" show_lengths)
            (setenv "ZZ_SHOW_SLOPES" show_slopes)

            (setq h_scale (atof h_scale))
            (setq l_scale (atof l_scale))
            (setq text_height (atof text_height))
            (setq round_to (atoi round_to))
            (setq slope_round_to (atoi slope_round_to))
            (setq use_text_height (= use_text_height "1"))
            (setq show_lengths (= show_lengths "1"))
            (setq show_slopes (= show_slopes "1"))

            (princ (strcat "\nМасштаб по высоте: " (rtos h_scale 2 2)))
            (princ (strcat "\nМасштаб по длине: " (rtos l_scale 2 2)))
            (princ (strcat "\nВысота текста: " (rtos text_height 2 2)))
            (princ (strcat "\nОкругление до: " (itoa round_to)))
            (princ (strcat "\nОкругление уклона до: " (itoa slope_round_to)))
            (princ (strcat "\nЕдиница уклона: " slope_unit))
            (princ (strcat "\nВысота из текста: " (if use_text_height "Да" "Нет")))
            (princ (strcat "\nПоказать длины: " (if show_lengths "Да" "Нет")))
            (princ (strcat "\nПоказать уклоны: " (if show_slopes "Да" "Нет")))

            (setq original_unitmode (getvar "UNITMODE"))
            (setq original_dimzin (getvar "DIMZIN"))
            (setq original_lunits (getvar "LUNITS"))
            (setq original_luprec (getvar "LUPREC"))

            (setvar "UNITMODE" 0)
            (setvar "DIMZIN" 0)
            (setvar "LUNITS" 2)
            (setvar "LUPREC" round_to)

            (if (= mode_points "1")
                (progn
                    (prompt "\nВыберите ось или край поперечника с известной высотой")
                    (setq OSZ (getpoint))
                    (if (null OSZ) (progn (princ "\nТочка с известной высотой не выбрана.") (exit)))
                    (if use_text_height
                        (progn
                            (prompt "\nВыберите текстовый объект с высотой: ")
                            (while (progn
                                    (setq text_entity (entsel))
                                    (if text_entity
                                        (not (member (cdr (assoc 0 (entget (car text_entity)))) '("TEXT" "MTEXT")))
                                        t
                                    )
                                  )
                                (princ "\nВыбранный объект не является текстом. Пожалуйста, выберите TEXT или MTEXT."))
                            (if (null text_entity) (progn (princ "\nТекстовый объект не выбран.") (exit)))
                            (setq text_entity (car text_entity))
                            (setq text_content (cdr (assoc 1 (entget text_entity))))
                            ; Замена запятой на точку для корректного преобразования
                            (setq text_content (vl-string-subst "." "," text_content))
                            (setq OSH (atof text_content))
                            (if (= OSH 0.0) (progn (princ "\nОшибка: не удалось преобразовать текст в число.") (exit)))
                        )
                        (progn
                            (prompt "\nВведите высоту: ")
                            (setq OSH (getreal))
                            (if (null OSH) (progn (princ "\nВысота не введена.") (exit)))
                        )
                    )
                    
                    (setq point_count 0)
                    (setq PCoords '())
                    (setq heights '())
                    (setq original_PCoords '())
                    (setq temp_points '())
                    
                    (prompt "\nУкажите точки профиля (Enter для завершения)")
                    (while (setq pt (getpoint (strcat "\nУкажите точку [" (itoa point_count) " точек]: ")))
                        (setq delta_y (- (cadr pt) (cadr OSZ)))
                        (setq final_height (+ OSH (* delta_y (/ 1.0 h_scale))))
                        (setq point_count (1+ point_count))
                        (setq PCoords (append PCoords (list pt)))
                        (setq original_PCoords (append original_PCoords (list pt)))
                        (setq heights (append heights (list final_height)))
                        (setq temp_point_ent (entmakex (list '(0 . "POINT") (cons 10 pt))))
                        (setq temp_points (append temp_points (list temp_point_ent)))
                        (princ (strcat "\nТочка добавлена [" (itoa point_count) " точек]"))
                    )
                    (foreach temp_point temp_points (if temp_point (entdel temp_point)))
                )
                (progn
                    (prompt "\nВыберите ось или край поперечника с известной высотой")
                    (setq OSZ (getpoint))
                    (if (null OSZ) (progn (princ "\nТочка с известной высотой не выбрана.") (exit)))
                    (if use_text_height
                        (progn
                            (prompt "\nВыберите текстовый объект с высотой: ")
                            (while (progn
                                    (setq text_entity (entsel))
                                    (if text_entity
                                        (not (member (cdr (assoc 0 (entget (car text_entity)))) '("TEXT" "MTEXT")))
                                        t
                                    )
                                  )
                                (princ "\nВыбранный объект не является текстом. Пожалуйста, выберите TEXT или MTEXT."))
                            (if (null text_entity) (progn (princ "\nТекстовый объект не выбран.") (exit)))
                            (setq text_entity (car text_entity))
                            (setq text_content (cdr (assoc 1 (entget text_entity))))
                            ; Замена запятой на точку для корректного преобразования
                            (setq text_content (vl-string-subst "." "," text_content))
                            (setq OSH (atof text_content))
                            (if (= OSH 0.0) (progn (princ "\nОшибка: не удалось преобразовать текст в число.") (exit)))
                        )
                        (progn
                            (prompt "\nВведите высоту: ")
                            (setq OSH (getreal))
                            (if (null OSH) (progn (princ "\nВысота не введена.") (exit)))
                        )
                    )
                    (prompt "\nВыберите вертикальные объекты: ")
                    (setq selected_entities (ssget))
                    (if (null selected_entities) (progn (princ "\nНе выбрано ни одного объекта.") (exit)))
                    
                    (setq filtered_entities '())
                    (setq i 0)
                    (while (< i (sslength selected_entities))
                        (setq entity (ssname selected_entities i))
                        (setq entity_type (cdr (assoc 0 (entget entity))))
                        (if (or (eq entity_type "LINE") (eq entity_type "LWPOLYLINE") (eq entity_type "POLYLINE"))
                            (setq filtered_entities (append filtered_entities (list entity)))
                        )
                        (setq i (1+ i))
                    )
                    (if (null filtered_entities) (progn (princ "\nНе найдено подходящих линий или полилиний.") (exit)))
                    
                    ; Фильтрация вертикальных объектов по X-координатам (удаление дубликатов с разницей < 0.01)
                    (setq x_coords '())
                    (setq unique_entities '())
                    (foreach entity filtered_entities
                        (setq entity_obj (vlax-ename->vla-object entity))
                        (setq start_pt (vlax-curve-getStartPoint entity_obj))
                        (setq x_coord (car start_pt))
                        (setq is_duplicate nil)
                        (foreach existing_x x_coords
                            (if (< (abs (- x_coord existing_x)) 0.01)
                                (setq is_duplicate t)
                            )
                        )
                        (if (not is_duplicate)
                            (progn
                                (setq x_coords (append x_coords (list x_coord)))
                                (setq unique_entities (append unique_entities (list entity)))
                            )
                        )
                    )
                    (setq filtered_entities unique_entities)
                    
                    (setq profile_polyline nil)
                    (while (null profile_polyline)
                        (prompt "\nВыберите профиль: ")
                        (setq profile_polyline (car (entsel)))
                        (if (null profile_polyline) 
                            (princ "\nПрофиль не выбран. Пожалуйста, выберите полилинию.")
                            (if (not (member (cdr (assoc 0 (entget profile_polyline))) '("LWPOLYLINE" "POLYLINE")))
                                (progn 
                                    (princ "\nВыбранный объект не является полилинией.")
                                    (setq profile_polyline nil)
                                )
                            )
                        )
                    )
                    (setq intersections '())
                    (foreach entity filtered_entities
                        (setq entity_obj (vlax-ename->vla-object entity))
                        (setq profile_polyline_obj (vlax-ename->vla-object profile_polyline))
                        (setq start_pt (vlax-curve-getStartPoint entity_obj))
                        (setq end_pt (vlax-curve-getEndPoint entity_obj))
                        (setq line_x (car start_pt))
                        (setq int_points (vlax-invoke profile_polyline_obj 'IntersectWith entity_obj acExtendBoth))
                        (if int_points
                            (progn
                                (setq i 0)
                                (while (< i (length int_points))
                                    (setq pt (list (nth i int_points) (nth (+ i 1) int_points) (nth (+ i 2) int_points)))
                                    (setq param (vlax-curve-getParamAtPoint profile_polyline_obj pt))
                                    (if (and param (>= param 0))
                                        (progn
                                            (setq intersections (append intersections (list pt)))
                                        )
                                    )
                                    (setq i (+ i 3))
                                )
                            )
                        )
                    )
                    (setq PCoords intersections)
                    (setq point_count (length PCoords))
                    (setq heights '())
                    (setq original_PCoords intersections)
                    (setq PCoords (vl-sort PCoords '(lambda (a b) (< (car a) (car b)))))
                    (setq original_PCoords PCoords)
                    (foreach pt PCoords
                        (setq delta_y (- (cadr pt) (cadr OSZ)))
                        (setq final_height (+ OSH (* delta_y (/ 1.0 h_scale))))
                        (setq heights (append heights (list final_height)))
                    )
                )
            )

            (prompt "\nУкажите верх и низ строки для размещения текста высоты")
            (while (null (setq top_point_height (getpoint "\nУкажите верхнюю точку строки для высоты: ")))
                (princ "\nВерхняя точка не выбрана. Пожалуйста, выберите точку."))
            (while (null (setq bottom_point_height (getpoint "\nУкажите нижнюю точку строки для высоты: ")))
                (princ "\nНижняя точка не выбрана. Пожалуйста, выберите точку."))

            (setq sorted_PCoords (vl-sort PCoords '(lambda (a b) (< (car a) (car b)))))
            (setq sorted_heights (mapcar '(lambda (pt) (nth (vl-position pt PCoords) heights)) sorted_PCoords))

            (setq prev_x (car (car sorted_PCoords)))
            (setq new_PCoords (list (car sorted_PCoords)))
            (setq i 1)
            (while (< i (length sorted_PCoords))
                (setq pt (nth i sorted_PCoords))
                (if (< (- (car pt) prev_x) text_height)
                    (setq pt (list (+ prev_x text_height) (cadr pt)))
                )
                (setq new_PCoords (append new_PCoords (list pt)))
                (setq prev_x (car pt))
                (setq i (1+ i))
            )
            (setq sorted_PCoords new_PCoords)

            (setq i 0)
            (while (< i (length sorted_PCoords))
                (setq pt (nth i sorted_PCoords))
                (setq final_height (nth i sorted_heights))
                (setq text_y_height (/ (+ (cadr top_point_height) (cadr bottom_point_height)) 2))
                (entmake 
                    (list
                        '(0 . "MTEXT")
                        '(100 . "AcDbEntity")
                        '(100 . "AcDbMText")
                        (cons 10 (list (car pt) text_y_height 0.0))
                        (cons 40 text_height)
                        (cons 1 (rtos final_height 2 round_to))
                        (cons 7 (getvar "TEXTSTYLE"))
                        '(71 . 5)
                        '(72 . 1)
                        '(50 . 1.5708)
                    )
                )
                (setq i (1+ i))
            )
            
            (if (and show_lengths (> point_count 0))
                (progn
                    (prompt "\nУкажите верх и низ строки для размещения текста длины")
                    (setq top_point_length (getpoint "\nУкажите верхнюю точку строки для длины: "))
                    (setq bottom_point_length (getpoint "\nУкажите нижнюю точку строки для длины: "))
                    (setq original_PCoords (vl-sort original_PCoords '(lambda (a b) (< (car a) (car b)))))
                    
                    (princ "\nТочки для линий длин: ")
                    (foreach pt original_PCoords
                        (princ (strcat "\n" (rtos (car pt) 2 2) ", " (rtos (cadr pt) 2 2)))
                    )
                    
                    (foreach pt original_PCoords
                        (entmake 
                            (list
                                '(0 . "LINE")
                                '(100 . "AcDbEntity")
                                '(100 . "AcDbLine")
                                (cons 10 (list (car pt) (cadr top_point_length) 0.0))
                                (cons 11 (list (car pt) (cadr bottom_point_length) 0.0))
                            )
                        )
                    )
                    
                    (setq prev_x (car (car original_PCoords)))
                    (foreach pt original_PCoords
                        (setq dist (* (- (car pt) prev_x) (/ 1.0 l_scale)))
                        (if (>= (abs (- (car pt) prev_x)) 0.01)
                            (progn
                                (setq dist (rtos dist 2 2))
                                (setq mid_point (/ (+ (car pt) prev_x) 2))
                                (setq mid_height (/ (+ (cadr top_point_length) (cadr bottom_point_length)) 2))
                                (setq text_angle 0)
                                (setq text_position mid_height)
                                (setq text_alignment 5)
                                (if (< (- (car pt) prev_x) (* text_height 2))
                                    (progn
                                        (setq text_angle 1.5708)
                                        (setq text_alignment 3)
                                        (if (< (- (car pt) prev_x) text_height)
                                            (progn
                                                (setq text_angle 0)
                                                (setq text_position (- (cadr bottom_point_length) text_height 0.01))
                                                (setq text_alignment 5)
                                            )
                                        )
                                    )
                                )
                                (if (< (- (car pt) prev_x) text_height)
                                    (progn
                                        (command "mleader"
                                                 (list mid_point (cadr bottom_point_length))
                                                 (list mid_point (- (cadr bottom_point_length) text_height))
                                                 dist
                                                 ""
                                                 "")
                                    )
                                    (progn
                                        (entmake 
                                            (list
                                                '(0 . "MTEXT")
                                                '(100 . "AcDbEntity")
                                                '(100 . "AcDbMText")
                                                (cons 10 (list mid_point text_position 0.0))
                                                (cons 40 text_height)
                                                (cons 1 dist)
                                                (cons 7 (getvar "TEXTSTYLE"))
                                                (cons 71 text_alignment)
                                                '(71 . 5)
                                                (cons 50 text_angle)
                                            )
                                        )
                                    )
                                )
                            )
                        )
                        (setq prev_x (car pt))
                    )
                )
            )

            (if (and show_slopes (> point_count 1))
                (progn
                    (prompt "\nУкажите верх и низ строки для размещения текста уклона")
                    (setq top_point_slope (getpoint "\nУкажите верхнюю точку строки для уклона: "))
                    (setq bottom_point_slope (getpoint "\nУкажите нижнюю точку строки для уклона: "))
                    (setq sorted_original_PCoords (vl-sort original_PCoords '(lambda (a b) (< (car a) (car b)))))
                    
                    (princ "\nТочки для линий уклонов: ")
                    (foreach pt sorted_original_PCoords
                        (princ (strcat "\n" (rtos (car pt) 2 2) ", " (rtos (cadr pt) 2 2)))
                    )
                    
                    (foreach pt sorted_original_PCoords
                        (entmake 
                            (list
                                '(0 . "LINE")
                                '(100 . "AcDbEntity")
                                '(100 . "AcDbLine")
                                (cons 10 (list (car pt) (cadr top_point_slope) 0.0))
                                (cons 11 (list (car pt) (cadr bottom_point_slope) 0.0))
                            )
                        )
                    )
                    
                    (setq i 1)
                    (while (< i (length sorted_original_PCoords))
                        (setq pt1 (nth (1- i) sorted_original_PCoords))
                        (setq pt2 (nth i sorted_original_PCoords))
                        (setq delta_x (- (car pt2) (car pt1)))
                        (setq delta_y (- (cadr pt2) (cadr pt1)))
                        (setq delta_x_scaled (/ delta_x l_scale))
                        (setq delta_y_scaled (/ delta_y h_scale))
                        (if (>= (abs delta_x_scaled) 0.01)
                            (progn
                                (if (/= delta_x_scaled 0)
                                    (progn
                                        (cond
                                            ((eq slope_unit "permille")
                                             (setq slope (* (/ (abs delta_y_scaled) delta_x_scaled) 1000))
                                             (setq slope_text (strcat (rtos slope 2 slope_round_to) "‰")))
                                            ((eq slope_unit "degrees")
                                             (setq slope (* (/ (atan (abs delta_y_scaled) delta_x_scaled) (/ pi 180)) 1))
                                             (setq slope_text (strcat (rtos slope 2 slope_round_to) "°")))
                                            ((eq slope_unit "ratio")
                                             (setq slope (/ (abs delta_y_scaled) delta_x_scaled))
                                             (setq slope_text (strcat "1:" (rtos (/ 1 slope) 2 slope_round_to))))
                                        )
                                        (setq text_x (if (> delta_y_scaled 0) (car pt1) (car pt2))) ; Правая черточка для уклона влево, левая для уклона вправо
                                        (setq text_alignment (if (> delta_y_scaled 0) 1 3)) ; 1 = верх лево, 3 = верх право
                                        (entmake 
                                            (list
                                                '(0 . "MTEXT")
                                                '(100 . "AcDbEntity")
                                                '(100 . "AcDbMText")
                                                (cons 10 (list text_x (cadr top_point_slope) 0.0))
                                                (cons 40 text_height)
                                                (cons 1 slope_text)
                                                (cons 7 (getvar "TEXTSTYLE"))
                                                (cons 71 text_alignment)
                                                '(72 . 1)
                                                '(50 . 0)
                                            )
                                        )
                                        (if (> delta_y_scaled 0)
                                            (entmake 
                                                (list
                                                    '(0 . "LINE")
                                                    '(100 . "AcDbEntity")
                                                    '(100 . "AcDbLine")
                                                    (cons 10 (list (car pt2) (cadr top_point_slope) 0.0))
                                                    (cons 11 (list (car pt1) (cadr bottom_point_slope) 0.0))
                                                )
                                            )
                                            (entmake 
                                                (list
                                                    '(0 . "LINE")
                                                    '(100 . "AcDbEntity")
                                                    '(100 . "AcDbLine")
                                                    (cons 10 (list (car pt1) (cadr top_point_slope) 0.0))
                                                    (cons 11 (list (car pt2) (cadr bottom_point_slope) 0.0))
                                                )
                                            )
                                        )
                                    )
                                    (princ "\nОшибка: точки на одной вертикали, уклон не рассчитан.")
                                )
                            )
                            (princ "\nТочки слишком близко друг к другу, уклон не рассчитан.")
                        )
                        (setq i (1+ i))
                    )
                )
            )

            (setvar "UNITMODE" original_unitmode)
            (setvar "DIMZIN" original_dimzin)
            (setvar "LUNITS" original_lunits)
            (setvar "LUPREC" original_luprec)
        )
    )
    (princ)
)
